module kea-ctrl-agent {
  yang-version 1.1;
  namespace "urn:ietf:params:xml:ns:yang:kea-ctrl-agent";
  prefix "kea-ctrl-agent";

  import ietf-inet-types {
    prefix inet;
  }
  import kea-types {
    prefix kea;
    revision-date 2025-06-25;
  }

  organization "Internet Systems Consortium";
  contact "kea-dev@lists.isc.org";
  description "This model defines a YANG data model that can be
               used to configure and manage a Kea control agent.";

  revision 2025-06-25 {
    description "Added HTTP/HTTPS control socket types.
                 Added trust-anchor, cert-file, key-file, cert-required
                 authentication and http-headers parameters to control sockets.";
  }

  revision 2019-08-12 {
    description "Initial revision";
    reference "";
  }

  /*
  * Data Nodes
  */

  container config {
    // config true;
    description "Contains control agent configuration.";

    leaf http-host {
      type inet:ip-address;
      description "IP address to which HTTP service will be bound.";
    }

    leaf http-port {
      type uint16;
      description "Port to which HTTP service will be bound.";
    }

    container control-sockets {
      description "Control sockets.";
      list control-sockets {
        key server-type;
        description "List of server control socket.";
        leaf server-type {
          type enumeration {
            enum "dhcp4" {
              description "kea-dhcp4 server";
            }
            enum "dhcp6" {
              description "kea-dhcp6 server";
            }
            enum "d2" {
              description "kea-dhcp-ddns server";
            }
          }
          mandatory true;
          description "Server type.";
        }
        container control-socket {
          description "Control socket information.";
          uses kea:control-socket-info;
        }
      }
    }

    uses kea:control-socket-tls;
    uses kea:http-headers;
    uses kea:authentication;

    uses kea:hooks-libraries;

    leaf user-context {
      type kea:user-context;
      description "Control agent user context.";
    }

    uses kea:loggers;
  }
}
