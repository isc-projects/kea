module kea-control-agent {
  yang-version 1.1;
  namespace "urn:ietf:params:xml:ns:yang:kea-control-agent";
  prefix "kea-control-agent";

  import ietf-inet-types {
    prefix inet;
  }
  import kea-types {
    prefix kea;
  }
  import kea-logging {
    prefix logging;
  }

  organization "Internet Systems Consortium";
  contact "kea-dev@lists.isc.org";
  description "This model defines a YANG data model that can be
               used to configure and manage a Kea control agent.";

  revision 2018-08-20 {
    description "Initial revision";
    reference "";
  }

  /*
  * Data Nodes
  */

  container config {
    // config true;
    description "Contains control agent configuration.";

    leaf http-host {
      type inet:ip-address;
      default "127.0.0.1";
      description "IP address to which HTTP service will be bound.";
    }

    leaf http-port {
      type uint16;
      default 8000;
      description "Port to which HTTP service will be bound.";
    }

    container control-sockets {
      description "Control sockets.";
      list socket {
        key server-type;
        description "List of server control socket.";
        leaf server-type {
          type enumeration {
            enum "dhcp4" {
              description "kea-dhcp4 server";
            }
            enum "dhcp6" {
              description "kea-dhcp6 server";
            }
            enum "d2" {
              description "kea-dhcp-ddns server";
            }
          }
          mandatory true;
          description "Server type.";
        }
        container control-socket {
          description "Control socket information.";
          uses kea:control-socket;
        }
      }
    }

    uses kea:hooks-libraries;

    leaf user-context {
      type kea:user-context;
      description "Control agent user context.";
    }
  }

  container logging {
    // config true;
    description "Logging";

    uses logging:configuration;
  }
}
