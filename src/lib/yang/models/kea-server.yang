module kea-server {
  yang-version 1.1;
  namespace "urn:ietf:params:xml:ns:yang::kea-server";
  prefix "kea-server";

  import kea-dhcp4 {
    prefix dhcp4;
  }
  import kea-dhcp6 {
    prefix dhcp6;
  }
  import kea-dhcpddns {
    prefix d2;
  }
  import kea-control-agent {
    prefix agent;
  }
  import kea-logging {
    prefix logging;
  }

  organization "Internet Systems Consortium";
  contact "kea-dev@lists.isc.org";
  description "This model defines a YANG data model that can be
    used to define some commonly used Kea server";

  revision 2018-08-20 {
    description "Initial revision";
    reference "";
  }

  /*
  * Data Nodes
  */
  container dhcp4 {
    presence "Enables DHCPv4 server";
    description "DHCPv4 server configuration";

    uses dhcp4:configuration;
  }

  container dhcp6 {
    presence "Enables DHCPv6 server";
    description "DHCPv6 server configuration";

    uses dhcp6:configuration;
  }

  container dhcpddns {
    presence "Enables DHCP-DDNS server";
    description "DHCP-DDNS server configuration";

    uses d2:configuration;
  }

  container control-agent {
    presence "Enables control agent";
    description "Control agent configuration";

    uses agent:configuration;
  }

  container logging {
    description "Logging";

    uses logging:configuration;
  }

  /*
  * State data
  */
  container state {
    config true;

    container dhcp4 {
      description "DHCPv4 server state.";
      uses dhcp4:state;
    }

    container dhcp6 {
      description "DHCPv6 server state.";
      uses dhcp6:state;
    }
  }
}
