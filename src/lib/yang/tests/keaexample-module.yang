module keaexample-module {
  yang-version 1.1;
  namespace "urn:ietf:params:xml:ns:yang:keaexample-module";
  prefix tm;

  import ietf-inet-types {
    prefix inet;
  }

  organization "Sysrepo and ISC";
  description
    "ISC imported an example module from Sysrepo tests and adapted it
     to kea testing regime.";
  contact
    "kea-dev@lists.isc.org";

   container container {
      config true;
      list list {
         leaf leaf {
            type string;
         }
         leaf key1 {
            type string;
         }
         leaf key2 {
            type string;
         }
         key "key1 key2";
      }
   }
}
